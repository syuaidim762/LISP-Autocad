(defun c:HG ()
  (if (eq (getvar "FILLMODE") 1)
    (setvar "FILLMODE" 0)
    (setvar "FILLMODE" 1)
  )
  (command "REGEN")
  (princ (strcat "\nHatches are now " (if (= (getvar "FILLMODE") 1) "VISIBLE" "HIDDEN")))
  (princ)
)
